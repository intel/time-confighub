// SPDX-FileCopyrightText: 2026 Intel Corporation
// SPDX-License-Identifier: BSD-3-Clause

/*
* Module Structure
* ================
*
* module intel-tcc-config
*	  └── leaf profile-id
*   ├── leaf profile-description
*   ├── container core-isolation
*   │   └── list core-assignment [core-id]
*   │       ├── leaf core-id
*   │       └── leaf isolate
*   │
*   ├── container core-frequency
*   │   ├── list frequency-profile [profile-id]
*   │   │   ├── leaf profile-id
*	  │   │   ├── container frequency
*	  │   │   │   ├── leaf governor         (enum: performance|powersave|
*	  │   │   │   │                                ondemand|schedutil|
*	  │   │   │   │                                userspace|conservative)
*	  │   │   │   ├── leaf min-freq-mhz
*	  │   │   │   ├── leaf max-freq-mhz
*	  │   │   │   └── must: perf -> min==max, max>=min
*	  │   │   └── container idle
*	  │   │       ├── leaf enable-all
*	  │   │       ├── leaf disable-by-latency-us
*	  │   │       └── list state-override [state-id]
*	  │   │           ├── leaf state-id
*	  │   │           └── leaf action           (disable | enable)
*	  │   └── container profile-assignment
*	  │       └── list core-assignment [core-id]
*	  │           ├── leaf core-id
*	  │           └── leaf profile-ref          (leafref -> frequency-profile)
*	  │
*	  ├── container uncore-frequency
*	  │   └── list core-ring-freq [core-id]
*	  │       ├── leaf core-id
*	  │       ├── leaf min-ring-ratio
*	  │       ├── leaf max-ring-ratio
*	  │       └── must: min == max
*	  │
*	  └── container platform-qos-resource-config
*		  └── list core-pqr-assoc [core-id]
*			  ├── leaf core-id
*			  ├── leaf class-of-service-id
*		    └── container resource-monitoring
*				  ├── leaf enabled
*				  ├── leaf rmid-id              (when enabled=true)
*				  └── leaf rmid-label           (when enabled=true)
 */

module intel-tcc-config {
  yang-version "1.1";
  namespace "urn:intel:params:xml:ns:yang:intel-tcc-config";
  prefix tcc;

  organization
    "Intel Corporation";

  contact
    "Author: Hea Ming, Su <hea.ming.su@intel.com>";

  description
    "Data model for Intel Time Coordinated Computing (TCC)
    platform tuning.

    Four subsystems are configured, listed in their required
    application order:
      1. core-isolation  -- Core isolation
      2. core-frequency   -- frequency scaling and C-state control
      3. uncore-frequency
                         -- ring/uncore bus frequency
      4. platform-qos-resource-config
                         -- L3 cache allocation (CAT) and optional
                            resource monitoring (CMT/MBM)";

  reference
    "Intel 64 and IA-32 Architectures Software Developer's Manual,
    Vol. 3B, Section 17.19 (Intel RDT);
    Intel Time Coordinated Computing (TCC) User Guide
    (Public Version 1) -- 2026 edition";

  revision 2026-06-18 {
    description
      "Renamed cpu-scheduling and cpu-frequency. ";
  }

  revision 2026-05-20 {
    description
      "Remove multi-instance support for tcc-configs.";
  }

  revision 2026-04-14 {
    description
      "Add multi-instance support for tcc-configs.";
  }

  revision 2026-04-08 {
    description
      "Initial version. Covers cpu-scheduling, cpu-frequency, uncore-frequency,
      and platform-qos-resource-config subsystems.";
    reference
      "Intel Time Coordinated Computing (TCC) User Guide
      (Public Version 1) -- 2026 edition";
  }

  // -----------------------------------------------------------------------
  // Typedefs
  // -----------------------------------------------------------------------

  typedef core-id-type {
    type uint32 {
      range "0..65535";
    }
    description
      "Logical Core (hardware thread) identifier as reported by the OS.
      The valid range is implementation-specific.";
  }

  typedef frequency-mhz-type {
    type uint32 {
      range "1..1000000";
    }
    units "megahertz";
    description
      "Core or bus frequency expressed in MHz.
      The supported range of values is implementation-specific.";
  }

  typedef governor-type {
    type enumeration {
      enum performance {
        description
          "Run the Core at the maximum allowed frequency at all times.
          Recommended for real-time and latency-sensitive workloads.";
      }
      enum powersave {
        description
          "Run the Core at the minimum allowed frequency at all times.
          Recommended for housekeeping or non-critical cores to save power.";
      }
      enum ondemand {
        description
          "Scale frequency up quickly when load increases, and down gradually
          when load decreases.";
      }
      enum schedutil {
        description
          "Scale frequency based on Core utilization information provided by
          the kernel scheduler.";
      }
      enum userspace {
        description
          "Allow an external application to set the Core frequency directly.
          No automatic scaling is performed.";
      }
      enum conservative {
        description
          "Scale frequency up and down gradually in response to load changes.
          Less aggressive than ondemand.";
      }
    }
    description
      "Linux CPUFreq scaling governor.
      The set of governors available on a given platform is implementation-specific
      and depends on the active CPUFreq driver and kernel configuration.";
  }

  typedef state-action-type {
    type enumeration {
      enum disable {
        description
          "Disable this C-state for the target Core.";
      }
      enum enable {
        description
          "Re-enable this C-state for the target Core.";
      }
    }
    description
      "Action to apply to an individual Core idle state (C-state).";
  }

  typedef ring-ratio-type {
    type uint8 {
      range "0..255";
    }
    description
      "Intel ring/uncore bus frequency expressed as a multiplier of
      the platform base clock (typically 100 MHz).
      The supported range of values is implementation-specific.";
  }

  typedef clos-id-type {
    type uint8 {
      range "0..15";
    }
    description
      "Intel Resource Director Technology (RDT) Class of Service identifier (CLOSID).
      Each CLOSID selects a cache allocation bitmask that governs L3 cache-way
      access for assigned Cores. The number of supported CLOSIDs is implementation-specific
      and may be fewer than 16.";
  }

  typedef rmid-type {
    type uint16 {
      range "1..1023";
    }
    description
      "Intel Resource Director Technology (RDT) Resource Monitoring ID
      (RMID) used for L3 cache occupancy and memory bandwidth telemetry.
      RMID 0 is reserved by hardware to indicate 'no monitoring'.
      The number of supported RMIDs is implementation-specific
      and may be fewer than the predefined range 1..1023.";
  }

  // -----------------------------------------------------------------------
  // Top-level container
  // -----------------------------------------------------------------------

container tcc-config {

  // -------------------------------------------------------------------
  // TCC Configuration Profile information
  // -------------------------------------------------------------------

  description
    "A named TCC platform tuning configuration Profile.";

  leaf profile-id {
    type string {
      length "1..64";
      pattern '[a-zA-Z_][a-zA-Z0-9_.\-]*';
    }
    description
      "Unique identifier for this TCC configuration profile.
      Examples: 'production-rt', 'debug'.";
  }

  leaf profile-description {
    type string {
      length "1..256";
    }
    description
      "Human-readable description of this configuration profile.";
  }

  // -------------------------------------------------------------------
  // 1. Core Isolation
  // -------------------------------------------------------------------

  container core-isolation {
    description
      "Per-Core isolation settings.  Isolated Cores are removed from
      the default scheduling and interrupt affinity masks so that
      only explicitly assigned real-time tasks execute on them.";

    list core-assignment {
      key "core-id";
      description
        "Isolation setting for a single logical Core.";

      leaf core-id {
        type core-id-type;
        description
          "Logical Core to configure.";
      }

      leaf isolate {
        type boolean;
        default false;
        description
          "When true, the Core is isolated from general-purpose scheduling
          and default IRQ delivery.";
      }
    }
  }

  // -------------------------------------------------------------------
  // 2. Core Frequency (C-state + frequency scaling)
  // -------------------------------------------------------------------

  container core-frequency {
    description
      "Per-Core frequency scaling and idle state (C-state) configuration.
      Settings are grouped into named profiles that can be shared
      across multiple Cores via profile-assignment.";

    list frequency-profile {
      key "profile-id";
      description
        "A named frequency and idle configuration profile.";

      leaf profile-id {
        type string {
          length "1..64";
        }
        description
          "Unique human-readable identifier for this profile.
          Examples: 'rt-core', 'housekeeping', 'fixed-3100MHz'.";
      }

      container frequency {
        description
          "Core frequency scaling parameters for this profile.";

        must "governor != 'performance' or min-freq-mhz = max-freq-mhz" {
          error-message
            "When governor is 'performance', min-freq-mhz must equal
            max-freq-mhz to achieve a fixed operating frequency.";
        }

        must "max-freq-mhz >= min-freq-mhz" {
          error-message
            "max-freq-mhz must be greater than or equal to min-freq-mhz.";
        }

        leaf governor {
          type governor-type;
          mandatory true;
          description
            "Frequency scaling governor to apply.";
        }

        leaf min-freq-mhz {
          type frequency-mhz-type;
          mandatory true;
          description
            "Minimum Core operating frequency in MHz.";
        }

        leaf max-freq-mhz {
          type frequency-mhz-type;
          mandatory true;
          description
            "Maximum Core operating frequency in MHz.";
        }
      }

      container idle {
        description
          "Core idle state (C-state) control for this profile.
          Three mechanisms are applied in order: enable-all first,
          disable-by-latency-us second, and state-override last.
          The available C-state indices are implementation-specific.";

        leaf enable-all {
          type boolean;
          default false;
          description
            "When true, re-enable all C-states before applying
            any disable operations.";
        }

        leaf disable-by-latency-us {
          type uint32;
          units "microseconds";
          description
            "Disable all C-states whose exit latency exceeds this
            value in microseconds.";
        }

        list state-override {
          key "state-id";
          description
            "Per-state enable or disable override.  Entries here
            take precedence over enable-all and
            disable-by-latency-us.";

          leaf state-id {
            type uint8 {
              range "0..31";
            }
            description
              "C-state index to override.  The mapping of indices
              to states is implementation-specific.";
          }

          leaf action {
            type state-action-type;
            mandatory true;
            description
              "Action to apply to this C-state.";
          }
        }
      }
    }

    container profile-assignment {
      description
        "Maps logical Cores to frequency profiles.";

      list core-assignment {
        key "core-id";
        description
          "Assigns a logical Core to a named frequency profile.";

        leaf core-id {
          type core-id-type;
          description
            "Logical Core to assign.";
        }

        leaf profile-ref {
          type leafref {
            path "../../../frequency-profile/profile-id";
          }
          mandatory true;
          description
            "Reference to the frequency-profile that governs this
            Core's frequency scaling and idle state policy.";
        }
      }
    }
  }

  // -------------------------------------------------------------------
  // 3. Uncore / Ring Bus Frequency
  // -------------------------------------------------------------------

  container uncore-frequency {
    description
      "Per-Core ring/uncore bus frequency configuration.
      Locking the ring frequency eliminates latency variation
      caused by dynamic frequency scaling transitions.";

    list core-ring-freq {
      key "core-id";
      description
        "Ring frequency setting for one logical Core.";

      must "min-ring-ratio = max-ring-ratio" {
        error-message
          "min-ring-ratio must equal max-ring-ratio to lock the
          ring bus at a constant frequency.";
      }

      leaf core-id {
        type core-id-type;
        description
          "Logical Core to configure.";
      }

      leaf min-ring-ratio {
        type ring-ratio-type;
        mandatory true;
        description
          "Minimum ring bus frequency ratio.";
      }

      leaf max-ring-ratio {
        type ring-ratio-type;
        mandatory true;
        description
          "Maximum ring bus frequency ratio.";
      }
    }
  }

  // -------------------------------------------------------------------
  // 4. Platform QoS Resource Configuration (L3 CAT + CMT/MBM)
  // -------------------------------------------------------------------

  container platform-qos-resource-config {
    description
      "Per-Core L3 cache allocation (Class of Service) assignment
      and optional cache/memory bandwidth monitoring configuration
      via Intel Resource Director Technology (RDT).";

    list core-pqr-assoc {
      key "core-id";
      description
        "CLOS and monitoring assignment for one logical Core.";

      leaf core-id {
        type core-id-type;
        description
          "Logical Core to configure.";
      }

      leaf class-of-service-id {
        type clos-id-type;
        mandatory true;
        description
          "Class of Service (CLOS) to assign to this Core.
          Determines which L3 cache-way allocation bitmask
          applies to this Core's memory accesses.";
      }

      container resource-monitoring {
        description
          "Optional L3 cache occupancy and memory bandwidth
          monitoring for this Core via Intel RDT.";

        leaf enabled {
          type boolean;
          default false;
          description
            "When true, L3 cache and memory bandwidth monitoring
            is active for this Core.  When false (default), no
            monitoring slot is consumed.";
        }

        leaf rmid-id {
          when "../enabled = 'true'" {
            description
              "Only present when monitoring is enabled.";
          }
          type rmid-type;
          mandatory true;
          description
            "Resource Monitoring ID (RMID) to assign to this Core.";
        }

        leaf rmid-label {
          when "../enabled = 'true'" {
            description
              "Only present when monitoring is enabled.";
          }
          type string {
            length "1..64";
          }
          description
            "Human-readable label for this monitoring slot.
            Used for documentation and tooling display only;
            has no effect on the hardware configuration.";
        }
      }
    }
  }
}
}
